package Requirements

section "Heading" {

    PlantUML context_diagram {
        file_path   = "diagram.puml"
        caption     = "Context diagram"
    }

    Requirement req_id_simple {
        description = "This is a simple requirement."
    }
}
